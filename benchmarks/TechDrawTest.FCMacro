# Generated by scripts/package_test_macro.py; edit the Python sources instead.
# Standalone: no extra Python files or packages to install.
"""FreeCAD GUI-step benchmark using document APIs and Qt widgets, never scene items."""
import hashlib
import json
import math
import os
from pathlib import Path
import platform
import statistics
import tempfile
import time


def summary(samples):
    ordered = sorted(samples)
    if not ordered:
        return {'count': 0, 'status': 'unrun'}
    return {'count': len(ordered), 'status': 'measured',
            'median_ms': statistics.median(ordered),
            'p95_ms': ordered[math.ceil(0.95 * len(ordered)) - 1],
            'min_ms': ordered[0], 'max_ms': ordered[-1]}


class Runner:
    def __init__(self, App, Gui, QtCore, QtWidgets, config):
        self.App, self.Gui, self.QtCore = App, Gui, QtCore
        self.config = config
        self.doc = App.ActiveDocument
        if self.doc is None:
            raise RuntimeError('Open the same saved test drawing in each FreeCAD version first.')
        if not self.doc.FileName or not Path(self.doc.FileName).is_file():
            raise RuntimeError('The benchmark needs a saved FCStd fixture for a reproducible hash.')
        if Gui.activeDocument().Modified:
            raise RuntimeError('Use an unmodified saved fixture; save your work before benchmarking.')
        pages = [obj for obj in self.doc.Objects if obj.TypeId == 'TechDraw::DrawPage']
        page_name = config.get('page')
        self.page = self.doc.getObject(page_name) if page_name else (pages[0] if pages else None)
        if self.page is None or self.page.TypeId != 'TechDraw::DrawPage':
            raise RuntimeError('No TechDraw page found.')
        # The copy launcher has already displayed and flushed this exact page.
        if not config.get('page_already_shown', False):
            Gui.activeDocument().getObject(self.page.Name).show()
            Gui.updateGui()
        mdi = Gui.getMainWindow().findChild(QtWidgets.QMdiArea)
        window = mdi.activeSubWindow() if mdi else None
        views = window.findChildren(QtWidgets.QGraphicsView) if window else []
        if len(views) != 1:
            raise RuntimeError('Expected one graphics VIEW widget in the active TechDraw page.')
        self.view = views[0]  # QWidget only: no scene(), items(), or ownership manipulation
        self.viewport = self.view.viewport()
        self.saved_transform = self.view.transform()
        self.saved_scroll = (self.view.horizontalScrollBar().value(), self.view.verticalScrollBar().value())
        self.saved_selection = [(s.DocumentName, s.ObjectName, tuple(s.SubElementNames))
                                for s in Gui.Selection.getSelectionEx()]
        self.selection_diagnostics = bool(config.get('selection_diagnostics', False))
        names = (['edge_selection'] if self.selection_diagnostics else
                 ['redraw', 'zoom', 'pan', 'edge_selection', 'dimension_property_move'])
        self.samples = {name: [] for name in names}
        self.selection_phases = []
        self.selection_warmup = []
        self.notes = {}
        self.warmup = int(config.get('warmup', 5))
        self.repeats = int(config.get('repeats', 30))
        if not 0 <= self.warmup <= 100 or not 1 <= self.repeats <= 1000:
            raise ValueError('Invalid warmup/repeats (limits: 100/1000).')
        page_views = list(self.page.Views)
        edge_name = config.get('view')
        self.edge_view = self.doc.getObject(edge_name) if edge_name else next(
            (v for v in page_views if v.isDerivedFrom('TechDraw::DrawViewPart')), None)
        self.edge = config.get('edge', 'Edge1')
        dim_name = config.get('dimension')
        self.dimension = self.doc.getObject(dim_name) if dim_name else next(
            (v for v in page_views if v.TypeId == 'TechDraw::DrawViewDimension'), None)
        self.dimension_xy = (self.dimension.X.Value, self.dimension.Y.Value) if self.dimension else None
        self.output = Path(config.get('output', str(Path(tempfile.gettempdir()) / 'techdraw-benchmark.json')))
        self.result = {
            'schema': 1, 'label': config.get('label', 'unspecified'),
            'freecad': App.Version(), 'qt': QtCore.qVersion(), 'platform': platform.platform(),
            'fixture_sha256': hashlib.sha256(Path(self.doc.FileName).read_bytes()).hexdigest(),
            'page': self.page.Name, 'view': self.edge_view.Name if self.edge_view else None,
            'edge': self.edge, 'dimension': self.dimension.Name if self.dimension else None,
            'viewport_px': [self.viewport.width(), self.viewport.height()],
            'device_pixel_ratio': self.viewport.devicePixelRatioF(),
            'initial_transform': [getattr(self.saved_transform, f'm{r}{c}')() for r in range(1, 4) for c in range(1, 4)],
            'initial_scroll': self.saved_scroll,
            'warmup': self.warmup, 'repeats': self.repeats,
            'fixture_kind': config.get('fixture_kind', 'unspecified'),
            'renderer_note': config.get('renderer_note', 'record renderer/settings manually'),
            'metric': 'GUI step wall time incl. synchronous viewport repaint; not FPS or GPU completion',
        }
        if self.selection_diagnostics:
            prefs = App.ParamGet('User parameter:BaseApp/Preferences/Mod/TechDraw/General')
            mode = self.view.viewportUpdateMode()
            self.result['diagnostics'] = {
                'kind': 'selection-phases-v1',
                'navigation_preview_preference': prefs.GetBool('NavigationPreview', False),
                'partial_viewport_updates_preference': prefs.GetBool('PartialViewportUpdates', False),
                'viewport_class': self.viewport.metaObject().className(),
                'viewport_update_mode': int(getattr(mode, 'value', mode)),
                'viewport_visible': self.viewport.isVisible(),
                'viewport_region_empty': self.viewport.visibleRegion().isEmpty(),
                'open_document_count': len(App.listDocuments()),
                'document_object_count': len(self.doc.Objects),
                'page_view_count': len(page_views),
                'graphics_view_count': len(Gui.getMainWindow().findChildren(QtWidgets.QGraphicsView)),
                'note': 'Preferences do not prove patch presence. Timings include synchronous selection observers; no FPS or CPU profile.',
            }
        self.operations = iter((name, i) for name in self.samples for i in range(self.warmup + self.repeats))
        self.finished = False
        self.drag_transaction = False
        self.timer = QtCore.QTimer()
        self.timer.setSingleShot(True)
        self.timer.timeout.connect(self.step)

    def start(self):
        # Dimension updates are undone as one transaction; no files are saved.
        self.doc.openTransaction('TechDraw benchmark (temporary)')
        self.drag_transaction = True
        self.timer.start(100)
        return self

    def operation(self, name, i):
        self.last_selection_phases = {}
        def timed(phase, callback):
            if not self.selection_diagnostics or name != 'edge_selection':
                return callback()
            started = time.perf_counter_ns()
            value = callback()
            self.last_selection_phases[phase] = (time.perf_counter_ns() - started) / 1e6
            return value

        sign = 1 if i % 2 == 0 else -1
        if name == 'redraw':
            pass
        elif name == 'zoom':
            self.view.setTransform(self.saved_transform)
            self.view.scale(1.05 if sign > 0 else 0.95, 1.05 if sign > 0 else 0.95)
        elif name == 'pan':
            bar = self.view.horizontalScrollBar()
            base = self.saved_scroll[0]
            target = max(bar.minimum(), min(bar.maximum(), base + sign * 25))
            if bar.minimum() == bar.maximum() or target == bar.value():
                return 'No available scroll range; zoom in identically before both runs.'
            bar.setValue(target)
        elif name == 'edge_selection':
            if self.edge_view is None:
                return 'No drawing view on page.'
            timed('clear_selection', self.Gui.Selection.clearSelection)
            timed('add_selection', lambda: self.Gui.Selection.addSelection(
                self.doc.Name, self.edge_view.Name, self.edge))
            selected = timed('verify_selection', self.Gui.Selection.getSelectionEx)
            if not any(s.ObjectName == self.edge_view.Name and self.edge in s.SubElementNames for s in selected):
                raise RuntimeError('Edge selection was not accepted.')
        elif name == 'dimension_property_move':
            if self.dimension is None:
                return 'No dimension on page.'
            # Model-property move deliberately includes recompute. This is not a mouse drag.
            self.dimension.X = self.dimension_xy[0] + sign
            self.dimension.Y = self.dimension_xy[1]
            self.doc.recompute()
        timed('gui_update', self.Gui.updateGui)
        timed('viewport_repaint', self.viewport.repaint)
        return None

    def step(self):
        try:
            name, i = next(self.operations)
        except StopIteration:
            self.finish()
            return
        try:
            if i == 0:
                self.view.setTransform(self.saved_transform)
                self.view.horizontalScrollBar().setValue(self.saved_scroll[0])
                self.view.verticalScrollBar().setValue(self.saved_scroll[1])
                self.Gui.updateGui()
            started = time.perf_counter_ns()
            skipped = self.operation(name, i)
            elapsed = (time.perf_counter_ns() - started) / 1e6
            if skipped:
                self.notes[name] = skipped
            elif self.selection_diagnostics and i < self.warmup:
                self.selection_warmup.append({'total_ms': elapsed, 'phases_ms': self.last_selection_phases})
            elif i >= self.warmup:
                self.samples[name].append(elapsed)
                if self.selection_diagnostics:
                    self.selection_phases.append(self.last_selection_phases)
        except Exception as error:
            self.result['error'] = f'{type(error).__name__}: {error}'
            self.finish()
            return
        self.timer.start(0)

    def finish(self):
        if self.finished:
            return
        restore_started = time.perf_counter_ns()
        self.finished = True
        self.timer.stop()
        try:
            if self.drag_transaction:
                self.doc.abortTransaction()
                self.doc.recompute()
            self.view.setTransform(self.saved_transform)
            self.view.horizontalScrollBar().setValue(self.saved_scroll[0])
            self.view.verticalScrollBar().setValue(self.saved_scroll[1])
            self.Gui.Selection.clearSelection()
            for document, obj, subs in self.saved_selection:
                if subs:
                    for sub in subs:
                        self.Gui.Selection.addSelection(document, obj, sub)
                else:
                    self.Gui.Selection.addSelection(document, obj)
            self.Gui.updateGui()
        except Exception as error:
            self.result['restore_error'] = str(error)
        self.result['samples_ms'] = self.samples
        self.result['summary'] = {name: summary(values) for name, values in self.samples.items()}
        self.result['notes'] = self.notes
        if self.selection_diagnostics:
            self.result['selection_phases_ms'] = self.selection_phases
            self.result['selection_warmup'] = self.selection_warmup
            self.result['restore_ms'] = (time.perf_counter_ns() - restore_started) / 1e6
        self.output.parent.mkdir(parents=True, exist_ok=True)
        self.output.write_text(json.dumps(self.result, indent=2), encoding='utf-8')
        self.App.Console.PrintMessage(f'TechDraw benchmark written: {self.output}\n')


def start():
    import FreeCAD as App
    import FreeCADGui as Gui
    from PySide import QtCore, QtGui
    try:
        from PySide import QtWidgets
    except ImportError:
        QtWidgets = QtGui
    config_path = os.environ.get('TECHDRAW_BENCH_CONFIG')
    config = json.loads(Path(config_path).read_text(encoding='utf-8')) if config_path else {}
    return Runner(App, Gui, QtCore, QtWidgets, config).start()


"""Test a selected page; use a copy for model edits or unsaved input."""
from datetime import datetime
from pathlib import Path
import json
import hashlib
import shutil
import tempfile
import time
import uuid



def projection_snapshot(page):
    """Read public projection state, including projection-group children.

    A first edge is evidence of geometry, not proof that face extraction has ended.
    """
    pending = list(page.Views)
    seen, result = set(), []
    while pending:
        view = pending.pop(0)
        if view.Name in seen:
            continue
        seen.add(view.Name)
        pending.extend(getattr(view, 'Views', []))
        if not view.isDerivedFrom('TechDraw::DrawViewPart'):
            continue
        row = {'name': view.Name, 'type': view.TypeId, 'state': list(view.State)}
        try:
            row['first_edge_available'] = not view.getEdgeByIndex(1).isNull()
        except Exception as error:
            row['first_edge_available'] = False
            row['edge_error'] = f'{type(error).__name__}: {error}'
        result.append(row)
    return result


def start_interactive(selection_diagnostics=False):
    import FreeCAD as App
    import FreeCADGui as Gui
    from PySide import QtCore, QtWidgets

    parent = Gui.getMainWindow()
    title = 'TechDraw-Auswahldiagnose' if selection_diagnostics else 'TechDraw-Test'
    previous = getattr(App, '_techdraw_test_runner', None)
    if previous is not None and not previous.finished:
        QtWidgets.QMessageBox.information(parent, title, 'Ein Test läuft bereits.')
        return previous
    original = App.ActiveDocument
    if original is None:
        QtWidgets.QMessageBox.information(parent, title, 'Bitte zuerst deine Zeichnung öffnen.')
        return None
    pages = [obj for obj in original.Objects if obj.TypeId == 'TechDraw::DrawPage']
    if not pages:
        QtWidgets.QMessageBox.information(parent, title, 'Das Dokument enthält keine TechDraw-Seite.')
        return None
    names = [f'{page.Label} ({page.Name})' for page in pages]
    chosen, ok = QtWidgets.QInputDialog.getItem(
        parent, title, 'Zeichnungsblatt auswählen:',
        names, 0, False)
    if not ok:
        return None
    started = time.perf_counter_ns()
    page_name = pages[names.index(chosen)].Name
    original_name = original.Name
    selection = [(s.DocumentName, s.ObjectName, tuple(s.SubElementNames))
                 for s in Gui.Selection.getSelectionEx()]
    temporary = None
    test_doc = None
    copy_name = None
    progress = None
    preparation = {}
    output = None
    preparing = True
    use_existing = False
    trace = {'status': 'preparing', 'stage': 'initialize', 'page': page_name,
             'freecad': App.Version(), 'qt': QtCore.qVersion(),
             'freecad_home': App.getHomePath(), 'preparation_ms': preparation}

    def checkpoint(stage):
        trace['stage'] = stage
        trace['elapsed_ms'] = (time.perf_counter_ns() - started) / 1e6
        if preparing and output is not None:
            output.write_text(json.dumps(trace, indent=2), encoding='utf-8')

    def prepare(phase, callback):
        checkpoint(phase)
        before = time.perf_counter_ns()
        try:
            value = callback()
        finally:
            preparation[phase] = (time.perf_counter_ns() - before) / 1e6
            checkpoint(phase)
        return value

    def cleanup(restore_selection=True):
        # Only the document opened by this invocation may be discarded.
        if copy_name is not None and copy_name in App.listDocuments():
            Gui.getDocument(copy_name).Modified = False
            checkpoint('close_copy')  # FreeCAD may wait for running projection workers here.
            App.closeDocument(copy_name)
        if original_name in App.listDocuments():
            App.setActiveDocument(original_name)
        if restore_selection:
            Gui.Selection.clearSelection()
            for document, obj, subs in selection:
                for sub in subs or ('',):
                    Gui.Selection.addSelection(document, obj, sub)
        if temporary is not None:
            temporary.cleanup()
        if progress is not None:
            progress.close()

    class InteractiveRunner(Runner):
        def start(self):
            # Full tests edit only the disposable copy. Direct diagnostics select
            # edges only; neither path needs a cross-document undo transaction.
            self.started_at = time.perf_counter_ns()
            self.timer.start(100)
            return self

        def step(self):
            if progress.wasCanceled():
                self.result['error'] = 'Test vom Benutzer abgebrochen.'
                self.finish()
                return
            self.completed_steps += 1
            progress.setValue(min(self.completed_steps, self.total_steps - 1))
            super().step()

        def finish(self):
            if self.finished:
                return
            failures = []
            try:
                super().finish()
                failures.extend(self.result[key] for key in ('error', 'restore_error')
                                if self.result.get(key))
            except Exception as error:
                failures.append(f'Ergebnis konnte nicht geschrieben werden: {error}')
            run_finished = time.perf_counter_ns()
            try:
                cleanup(restore_selection=not use_existing or bool(self.result.get('restore_error')))
            except Exception as error:
                failures.append(f'Temporäre Testkopie konnte nicht aufgeräumt werden: {error}')
                if progress is not None:
                    progress.close()
            if self.selection_diagnostics:
                self.result['lifecycle_ms'] = {
                    'preparation': preparation,
                    'run_including_restore': (run_finished - self.started_at) / 1e6,
                    'cleanup': (time.perf_counter_ns() - run_finished) / 1e6,
                    'total_after_page_choice': (time.perf_counter_ns() - started) / 1e6,
                }
                if failures:
                    self.result['error'] = '\n'.join(failures)
                try:
                    self.output.write_text(json.dumps(self.result, indent=2), encoding='utf-8')
                except Exception as error:
                    failures.append(f'Diagnose konnte nicht geschrieben werden: {error}')
            if failures:
                QtWidgets.QMessageBox.warning(
                    parent, title, 'Test nicht erfolgreich abgeschlossen; diese Messung nicht '
                    'vergleichen.\n\n' + '\n'.join(failures) + f'\n\nErgebnisdatei: {self.output}')
                return
            labels = {'redraw': 'Neuzeichnen', 'zoom': 'Zoom', 'pan': 'Verschieben',
                      'edge_selection': 'Kantenauswahl per API',
                      'dimension_property_move': 'Maßposition per Eigenschaft'}
            rows = []
            for name, stats in self.result['summary'].items():
                if stats['count'] == self.repeats:
                    rows.append(f"{labels[name]}: {stats['median_ms']:.2f} ms "
                                f"(p95: {stats['p95_ms']:.2f} ms)")
                else:
                    rows.append(f'{labels[name]}: nicht vollständig gemessen '
                                '(z. B. kein Scrollbereich oder keine Bemaßung)')
            QtWidgets.QMessageBox.information(
                parent, title, '\n'.join(rows) + '\n\n' +
                ('Geometrie und Bemaßungen wurden nicht verändert; die Auswahl wurde wiederhergestellt. '
                 if use_existing else 'Dein Original wurde nicht bearbeitet. Die temporäre Testkopie wurde geschlossen. ') +
                'Kleinere Zeiten sind besser; '
                'dies misst keine FPS und kein tatsächliches Mausziehen.'
                f'\n\nErgebnis: {self.output}\n\nFür einen Vergleich dieselbe gespeicherte '
                'Zeichnung in beiden Versionen testen und die JSON-Dateien aufbewahren.')

    try:
        downloads = QtCore.QStandardPaths.writableLocation(QtCore.QStandardPaths.DownloadLocation)
        output_dir = Path(downloads) if downloads else Path.home() / 'Downloads'
        output_dir.mkdir(parents=True, exist_ok=True)
        output = output_dir / f'TechDraw-{datetime.now():%Y%m%d-%H%M%S}-{uuid.uuid4().hex[:8]}.json'
        checkpoint('initialize')
        try:
            import Part
            trace['occ'] = Part.OCC_VERSION
        except (ImportError, AttributeError):
            trace['occ'] = None
        progress = QtWidgets.QProgressDialog(
            'Temporäre Testkopie wird vorbereitet …', 'Abbrechen', 0, 66, parent)
        progress.setWindowTitle(title)
        progress.setWindowModality(QtCore.Qt.WindowModal)
        progress.setMinimumDuration(0)
        progress.setAutoClose(False)
        progress.setAutoReset(False)
        progress.setValue(0)
        saved_source = (bool(original.FileName) and Path(original.FileName).is_file()
                        and not Gui.getDocument(original_name).Modified)
        active_view = Gui.getDocument(original_name).activeView()
        active_page = active_view.getPage() if hasattr(active_view, 'getPage') else None
        use_existing = (selection_diagnostics and saved_source and active_page is not None
                        and active_page.Name == page_name)
        if use_existing:
            # Selection-only diagnostics do not change model properties or recompute.
            test_doc = original
            copy_path = Path(original.FileName)
            trace['copy_mode'] = 'existing-document'
            progress.setLabelText('Vorhandenes Blatt wird geprüft – keine erneute Dokumentkopie.')
        else:
            temporary = tempfile.TemporaryDirectory(prefix='techdraw-test-')
            copy_path = Path(temporary.name) / 'TechDrawTest.FCStd'
            if saved_source:
                # Preserve identical bytes/hashes for comparisons across FreeCAD versions.
                prepare('copy_saved_file', lambda: shutil.copy2(original.FileName, copy_path))
            else:
                # saveCopy includes unsaved edits without renaming/saving the original document.
                prepare('save_unsaved_snapshot', lambda: original.saveCopy(str(copy_path)))
            trace['copy_mode'] = 'saved-file' if saved_source else 'unsaved-snapshot'
            trace['fixture_sha256'] = hashlib.sha256(copy_path.read_bytes()).hexdigest()
            test_doc = prepare('open_copy', lambda: App.openDocument(str(copy_path)))
            copy_name = test_doc.Name
        trace['fixture_sha256'] = hashlib.sha256(copy_path.read_bytes()).hexdigest()
        trace['document_object_count'] = len(test_doc.Objects)
        trace['invalid_objects'] = [o.Name for o in test_doc.Objects if 'Invalid' in o.State]
        if not use_existing:
            prepare('recompute_copy', test_doc.recompute)
        test_page = test_doc.getObject(page_name)
        projected = next((v for v in test_page.Views
                          if v.isDerivedFrom('TechDraw::DrawViewPart')), None)
        timer = QtCore.QElapsedTimer()
        timer.start()
        last_snapshot = -1000
        while projected is not None:
            elapsed = timer.elapsed()
            if elapsed - last_snapshot >= 1000:
                trace['projection_state'] = projection_snapshot(test_page)
                preparation['wait_projection'] = elapsed
                checkpoint('wait_projection')
                last_snapshot = elapsed
            if progress.wasCanceled():
                trace['status'] = 'cancelled'
                trace['error'] = 'Vorbereitung vom Benutzer abgebrochen.'
                checkpoint('wait_projection')
                cleanup()
                checkpoint('cancelled')
                return None
            try:
                if not projected.getEdgeByIndex(1).isNull():
                    break
            except ValueError:
                pass
            if timer.elapsed() > 60000:
                raise RuntimeError(f'Die Testansicht {projected.Name} hat nach 60 Sekunden noch keine '
                                   'projizierte Kante. Die Vorbereitung wurde protokolliert.')
            loop = QtCore.QEventLoop()
            QtCore.QTimer.singleShot(20, loop.quit)
            loop.exec_()
        preparation['wait_projection'] = timer.elapsed()
        trace['projection_state'] = projection_snapshot(test_page)
        if not use_existing:
            App.setActiveDocument(test_doc.Name)
            prepare('show_page', Gui.getDocument(test_doc.Name).getObject(page_name).show)
            prepare('initial_gui_update', Gui.updateGui)
        # Recomputing the disposable copy may mark it modified. The original and
        # the copied input bytes remain untouched; only this temporary GUI flag resets.
        if not use_existing:
            Gui.getDocument(copy_name).Modified = False
        runner = prepare('initialize_runner', lambda: InteractiveRunner(App, Gui, QtCore, QtWidgets,
                                   {'page': page_name, 'label': 'automatic-copy', 'output': str(output),
                                    'page_already_shown': True,
                                    'warmup': 1 if selection_diagnostics else 3,
                                    'repeats': 3 if selection_diagnostics else 10,
                                    'selection_diagnostics': selection_diagnostics}))
        runner.result['source_label'] = original.Label
        runner.result['freecad_home'] = App.getHomePath()
        runner.result['copy_mode'] = trace['copy_mode']
        trace['status'] = 'prepared'
        checkpoint('prepared')
        # Runner owns this same output after setup; cleanup must not overwrite it.
        preparing = False
        runner.result['preparation_diagnostic'] = dict(trace)
        runner.total_steps = len(runner.samples) * (runner.warmup + runner.repeats) + 1
        runner.completed_steps = 0
        progress.setMaximum(runner.total_steps)
        progress.setLabelText('Zeichnungsblatt wird getestet. Bitte währenddessen nicht bearbeiten.\n' +
                             ('Nur Kantenauswahl: 1 Aufwärmschritt und 3 Messschritte.' if selection_diagnostics else
                              'Gemessen werden Neuzeichnen, Zoom, Verschieben, Auswahl und Maßposition.'))
        App._techdraw_test_runner = runner.start()
        return runner
    except Exception as error:
        trace['status'] = 'failed'
        trace['error'] = f'{type(error).__name__}: {error}'
        trace['failed_stage'] = trace['stage']
        try:
            checkpoint(trace['stage'])  # Persist BEFORE cleanup can wait for workers.
        except OSError:
            pass
        try:
            cleanup()
        except Exception as cleanup_error:
            trace['cleanup_error'] = str(cleanup_error)
            error = RuntimeError(f'{error}\nAufräumen: {cleanup_error}')
        try:
            checkpoint('failed')
        except OSError:
            pass
        report_path = f'\n\nDiagnose: {output}' if output is not None and output.is_file() else ''
        QtWidgets.QMessageBox.critical(parent, title, f'Test konnte nicht gestartet werden:\n{error}{report_path}')
        return None


TECHDRAW_TEST_RUNNER = start_interactive()
